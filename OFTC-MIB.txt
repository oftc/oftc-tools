OFTC-MIB DEFINITIONS ::= BEGIN
--- Copyright (C) 2007 Luca Filipozzi
--- vim: set ft=mib ts=4 sw=4 et:

IMPORTS
    MODULE-IDENTITY, OBJECT-TYPE
        FROM SNMPv2-SMI
    palfrader
        FROM PALFRADER-MIB;

oftc MODULE-IDENTITY
    LAST-UPDATED "200704070000Z"
    ORGANIZATION "Open and Free Technology Community"
    CONTACT-INFO "noc@oftc.net"
    DESCRIPTION  "intentionally empty"
    ::= { palfrader 7 }

oftcdns OBJECT IDENTIFIER ::= { oftc 1 }
statbot OBJECT IDENTIFIER ::= { oftc 2 }

END

-- Copyright (C) 2007 Luca Filipozzi
STATBOT-MIB DEFINITIONS ::= BEGIN

IMPORTS
    MODULE-IDENTITY, OBJECT-TYPE, Integer32
        FROM SNMPv2-SMI
    oftc
        FROM OFTC-MIB;

statbot MODULE-IDENTITY
    LAST-UPDATED "200704070000Z"
    ORGANIZATION "Open and Free Technology Community"
    CONTACT-INFO "noc@oftc.net"
    DESCRIPTION  "statbot"
    ::= { oftc 2 }

nodeCount OBJECT-TYPE
    SYNTAX      Integer32
    MAX-ACCESS  read-only
    STATUS      current
    DESCRIPTION "number of nodes in the node table"
    ::= { statbot 1 }

nodeTable OBJECT-TYPE
    SYNTAX      SEQUENCE OF NodeEntry
    MAX-ACCESS  not-accessible
    STATUS      current
    DESCRIPTION "node table (consisting of node entries)"
    ::= { statbot 2 }

nodeEntry OBJECT-TYPE
    SYNTAX      NodeEntry
    MAX-ACCESS  not-accessible
    STATUS      current
    DESCRIPTION "node entry"
    INDEX       { nodeIndex }
    ::= { nodeTable 1 }

NodeEntry ::=
    SEQUENCE {
        nodeIndex  Integer32,
        nodeName   DisplayString,
        nodeActive DisplayString
        nodeRank   Integer32,
    }

nodeIndex OBJECT-TYPE
   SYNTAX      Integer32
   MAX-ACCESS  not-accessible
   STATUS      current
   DESCRIPTION "node index"
   ::= { nodeEntry 1 }

nodeName OBJECT-TYPE
    SYNTAX      DisplayString
    MAX-ACCESS  read-only
    STATUS      current
    DESCRIPTION "node name"
    ::= { nodeEntry 2 }

nodeActive OBJECT-TYPE
    SYNTAX      DisplayString
    MAX-ACCESS  read-only
    STATUS      current
    DESCRIPTION "node active"
    ::= { nodeEntry 3 }

nodeRank OBJECT-TYPE
    SYNTAX      Integer32
    MAX-ACCESS  read-only
    STATUS      current
    DESCRIPTION "node active"
    ::= { nodeEntry 4 }

nodeLast OBJECT-TYPE
    SYNTAX      Integer32
    MAX-ACCESS  read-only
    STATUS      current
    DESCRIPTION "node last"
    ::= { nodeEntry 5 }

connectorState OBJECT-TYPE
    SYNTAX      DisplayString
    MAX-ACCESS  read-only
    STATUS      current
    DESCRIPTION "state of irc connector"
    ::= { statbot 3 }

END
-- vim: set ts=4 sw=4 et ft=mib:

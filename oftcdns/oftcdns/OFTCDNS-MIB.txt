-- Copyright (C) 2007 Luca Filipozzi
OFTCDNS-MIB DEFINITIONS ::= BEGIN

IMPORTS
    MODULE-IDENTITY, OBJECT-TYPE, Integer32
        FROM SNMPv2-SMI
    oftc
        FROM OFTC-MIB;

oftcdns MODULE-IDENTITY
    LAST-UPDATED "200704070000Z"
    ORGANIZATION "Open and Free Technology Community"
    CONTACT-INFO "noc@oftc.net"
    DESCRIPTION  "oftcdns"
    ::= { oftc 1 }

poolCount OBJECT-TYPE
    SYNTAX      Integer32
    MAX-ACCESS  read-only
    STATUS      current
    DESCRIPTION "number of pools in the pool table"
    ::= { oftcdns 1 }

poolTable OBJECT-TYPE
    SYNTAX      SEQUENCE OF PoolEntry
    MAX-ACCESS  not-accessible
    STATUS      current
    DESCRIPTION "pool table (consisting of pool entries)"
    ::= { oftcdns 2 }

poolEntry OBJECT-TYPE
    SYNTAX      PoolEntry
    MAX-ACCESS  not-accessible
    STATUS      current
    DESCRIPTION "pool entry"
    INDEX       { poolIndex }
    ::= { poolTable 1 }

PoolEntry ::=
    SEQUENCE {
        poolIndex  Integer32,
        poolName   DisplayString,
        nodeCount  Integer32,
    }

poolIndex OBJECT-TYPE
   SYNTAX      Integer32
   MAX-ACCESS  not-accessible
   STATUS      current
   DESCRIPTION "pool index"
   ::= { poolEntry 1 }

poolName OBJECT-TYPE
    SYNTAX      DisplayString
    MAX-ACCESS  read-only
    STATUS      current
    DESCRIPTION "pool name"
    ::= { poolEntry 2 }

nodeCount OBJECT-TYPE
    SYNTAX      Integer32
    MAX-ACCESS  read-only
    STATUS      current
    DESCRIPTION "number of nodes in the pool"
    ::= { poolEntry 3 }

END
-- vim: set ts=4 sw=4 et ft=mib:
